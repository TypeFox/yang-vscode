module ietf-inet-types {

    namespace "urn:ietf:params:xml:ns:yang:ietf-yang-types";
    prefix "yang";
    revision 2012-02-22 {
        description
          "dummy";
    }

    typedef port-number {
        type uint32;
    }
}
