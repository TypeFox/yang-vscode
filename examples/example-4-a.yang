module example-4-a {

  yang-version "1.1";

  namespace "http://example.com/example-4-a";

  prefix "ex4a";

  import ietf-netconf-acm {
    prefix "nacm";
    revision-date 2012-02-22;
  }

  container bag {
    description "Top-level container.";
    presence "true";
    container innerBag {
        leaf foo {
          type uint8;  
          mandatory "true";
          //nacm:default-deny-write;
        }
        leaf bar {
          type boolean;
          default "true";
          config "false";
        }
        leaf-list cipher {
          type string;
          ordered-by user;
          description
            "A list of ciphers.";
        }
        choice opts {
          default "a";
          case a {
            leaf baz {
              type empty;
            }
          }
        }
    }
  }

}
