module example-deviations {
    yang-version 1.1;
    namespace "urn:example:deviations";
    prefix md;

    import base-test-module {
        prefix base;
    }

    deviation /base:system/base:daytime {
        // server  does not support the "daytime" service
        deviate not-supported;
    }

    deviation /base:system/base:user/base:type {
        deviate add {
            // the users are admin by default
            default "admin";
        }
    }

    deviation /base:system/base:name-server {
        deviate replace {
            // the server limits the number of name servers to 3
            max-elements 3;
        }
    }

    deviation /base:system {
        deviate delete {
            // remove this "must" constraint
            must "daytime or time";
        }
	    deviate add {
            // add this "must" constraint
            must "time";
        }
    }
}
